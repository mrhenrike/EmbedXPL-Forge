VENTURI-SERVER-TRAP-MIB DEFINITIONS ::= BEGIN

IMPORTS
    NOTIFICATION-TYPE,
    MODULE-IDENTITY,
    OBJECT-IDENTITY,
    OBJECT-TYPE,
    Counter32,
    Counter64,
    Gauge32,
    Integer32
        FROM SNMPv2-SMI
    vServerMgmt
        FROM VENTURI-SERVER-MIB
;

-- ------------------------------------------------------------------------
-- Module Identity
-- ------------------------------------------------------------------------
vServerTraps MODULE-IDENTITY
    LAST-UPDATED    "201101030000Z"
    ORGANIZATION    "Venturi Wireless"
    CONTACT-INFO
       "Contact:  Customer Support

        Postal:   Venturi Wireless
                  490 North McCarthy Boulevard
                  Milpitas, CA  95035

        Phone:    408-215-5100
        FAX:      408-215-5105

        Web:      www.venturiwireless.com

        E-mail:   VenturiCustomerOps@venturiwireless.com"

    DESCRIPTION
        "The Trap MIB module for Venturi Wireless Server

          Copyright 2005-2011 Venturi Wireless
          All rights reserved.

          This MIB module specifies the traps that may be sent
          from a Venturi Wireless compression server."
    
    REVISION    "201101030000Z"
        DESCRIPTION 
            "1.5 - Updated copyright date to 2011"

    REVISION    "201001060000Z"
        DESCRIPTION 
            "1.4 - Updated copyright date to 2010"

    REVISION    "200806250000Z"
        DESCRIPTION
            "1.3 - Add entityId varbind to traps."
    
    REVISION    "200803190000Z"
        DESCRIPTION
            "1.2 - Add traps for Disconnection Log delivery
                   error and clear."

    REVISION    "200507120000Z"
        DESCRIPTION
            "1.1 - Add vServerStatsDeliveryClear, 
                       vServerLogDeliveryClear and
                       vServerURLDeliveryClear traps."
        
    REVISION    "200504250000Z"
        DESCRIPTION
            "1.0 - Initial document."


    ::= { vServerMgmt 1 }


-- --------------------------------------------
--  Divisions within traps
-- --------------------------------------------
vServerTrapDef OBJECT-IDENTITY
        STATUS	current
        DESCRIPTION
                "Traps are defined below this point."
        ::= { vServerTraps 0 }

vServerTrapInfo OBJECT-IDENTITY
        STATUS	current
        DESCRIPTION
                "The types of varbinds send with traps are defined
                 below this point."
        ::= { vServerTraps 1 }


-- ----------------------------
--  Traps
-- ----------------------------

vServerStopped NOTIFICATION-TYPE
    OBJECTS    { mCode, errorCode, systemId, trapSeverity, entityId }
    STATUS    current
    DESCRIPTION
        " Trap issued when Venturi software is shutting down. "

    --#TYPE      "Venturi Software stopped."
    --#SUMMARY   "VenturiServer: Software stopped. "
    --#SUMMARY   "If venturi Started alarm does not follow, contact Venturi."
    --#SEVERITY CRITICAL
    ::= { vServerTrapDef 1 }

vServerStarted NOTIFICATION-TYPE
    OBJECTS    { mCode, errorCode, systemId, trapSeverity, entityId }
    STATUS     current
    DESCRIPTION
        " Trap issued when Venturi software starts execution. "

    --#TYPE      "Venturi Software (re)start completed successfully."
    --#SUMMARY   "VenturiServer: Software (re)start completed successfully.  "
    --#SUMMARY   "If not intentional, contact Venturi."
    --#SEVERITY INFORMATIONAL
    ::= { vServerTrapDef 2 }

vServerSwapOverload NOTIFICATION-TYPE
    OBJECTS    { mCode, errorCode, systemId, trapSeverity, 
                 currentValue, setThreshold, clearThreshold, entityId }
    STATUS    current
    DESCRIPTION
        " Trap issued when the Venturi server is out of swap space.
        The current percent of swap space used (currentValue) and 
        the set and clear threshold percentages are included with 
        the trap.  The swap overload condition is set when a rising
        swap usage crosses the setThreshold."

    --#TYPE      "Swap Overload"
    --#SUMMARY   "VenturiServer: Low swap space (currently %d percent used). "
    --#SUMMARY   "Contact Venturi."
    --#ARGUMENTS  { 4 }
    --#SEVERITY MINOR
    ::= { vServerTrapDef 3 }

vServerSwapOverloadClear  NOTIFICATION-TYPE
    OBJECTS    { mCode, errorCode, systemId, trapSeverity, entityId }
    STATUS    current
    DESCRIPTION
        " Trap issued to indicate that swap usage has dropped below
        the clear threshold and the swap overload condition is no longer
        in effect. "

    --#TYPE      "Swap Overload Clear"
    --#SUMMARY   "VenturiServer: Clear to earlier Swap Overload problem. "
    --#SUMMARY   "No action; Venturi has returned to normal operation."
    --#SEVERITY INFORMATIONAL
    ::= { vServerTrapDef 4 }

vServerNetworkError  NOTIFICATION-TYPE
    OBJECTS    { mCode, errorCode, systemId, trapSeverity, entityId }
    STATUS    current
    DESCRIPTION
        "Trap generated due to problems related to network initialization."

    --#TYPE      "Network Error"
    --#SUMMARY   "VenturiServer: Network Initialization Error. "
    --#SUMMARY   "Reboot server; if problem persists, contact Venturi."
    --#SEVERITY CRITICAL
    ::= { vServerTrapDef 5 }

vServerNetworkErrorClear  NOTIFICATION-TYPE
    OBJECTS    { mCode, errorCode, systemId, trapSeverity, entityId }
    STATUS    current
    DESCRIPTION
        "Trap issued to indicate that the earlier problem with network
         initialization has been cleared."

    --#TYPE      "System Network Error Clear"
    --#SUMMARY   "VenturiServer: Clear to Network Interface Initialization Problem. "
    --#SUMMARY   "No action; Venturi has returned to normal operation."
    --#SEVERITY INFORMATIONAL
    ::= { vServerTrapDef 6 }

vServerKernelError  NOTIFICATION-TYPE
    OBJECTS    { mCode, errorCode, systemId, trapSeverity, entityId }
    STATUS    current
    DESCRIPTION
        "Trap generated due to problems related to the kernel."

    --#TYPE      "Kernel Error"
    --#SUMMARY   "VenturiServer: Kernel Errors. "
    --#SUMMARY   "Reboot server; if problem persists, contact Venturi."
    --#SEVERITY CRITICAL
    ::= { vServerTrapDef 7 }

vServerKernelErrorClear  NOTIFICATION-TYPE
    OBJECTS    { mCode, errorCode, systemId, trapSeverity, entityId }
    STATUS    current
    DESCRIPTION
        "Trap issued to indicate that the earlier problem with the kernel has
         been cleared."

    --#TYPE      "System Kernel Error Clear"
    --#SUMMARY   "VenturiServer: Clear to kernel problem. "
    --#SUMMARY   "No action; Venturi has returned to normal operation."
    --#SEVERITY INFORMATIONAL
    ::= { vServerTrapDef 8 }

vServerLicenseError  NOTIFICATION-TYPE
    OBJECTS    { mCode, errorCode, systemId, trapSeverity, entityId }
    STATUS    current
    DESCRIPTION
        "Trap generated due to problems related to hardware licensing."

    --#TYPE      "License Error"
    --#SUMMARY   "VenturiServer: Hardware Licensing Errors. "
    --#SUMMARY   "Reboot server; if problem persists, contact Venturi."
    --#SEVERITY CRITICAL
    ::= { vServerTrapDef 9 }

vServerLicenseErrorClear  NOTIFICATION-TYPE
    OBJECTS    { mCode, errorCode, systemId, trapSeverity, entityId }
    STATUS    current
    DESCRIPTION
        "Trap issued to indicate that the earlier problem with hardware
         licensing has been cleared."

    --#TYPE      "System License Error Clear"
    --#SUMMARY   "VenturiServer: Clear to license problem. "
    --#SUMMARY   "No action; Venturi has returned to normal operation."
    --#SEVERITY INFORMATIONAL
    ::= { vServerTrapDef 10 }

vServerSharedMemoryError  NOTIFICATION-TYPE
    OBJECTS    { mCode, errorCode, systemId, trapSeverity, entityId }
    STATUS    current
    DESCRIPTION
        "Trap generated due to problems related to shared memory."

    --#TYPE      "Shared Memory Error"
    --#SUMMARY   "VenturiServer: Shared memory errors. "
    --#SUMMARY   "Reboot server; if problem persists, contact Venturi."
    --#SEVERITY CRITICAL
    ::= { vServerTrapDef 11 }

vServerSharedMemoryErrorClear  NOTIFICATION-TYPE
    OBJECTS    { mCode, errorCode, systemId, trapSeverity, entityId }
    STATUS    current
    DESCRIPTION
        "Trap issued to indicate that the earlier problem with shared
         memory access has been cleared."

    --#TYPE      "System Shared Memory Error Clear"
    --#SUMMARY   "VenturiServer: Clear to Shared Memory problem. "
    --#SUMMARY   "No action; Venturi has returned to normal operation."
    --#SEVERITY INFORMATIONAL
    ::= { vServerTrapDef 12 }

vServerFileSystemError  NOTIFICATION-TYPE
    OBJECTS    { mCode, errorCode, systemId, trapSeverity, entityId }
    STATUS    current
    DESCRIPTION
        " Trap generated due to problems related to the file system."

    --#TYPE      "File System Error"
    --#SUMMARY   "VenturiServer: File System Errors. "
    --#SUMMARY   "Reboot server; if problem persists, contact Venturi."
    --#SEVERITY CRITICAL
    ::= { vServerTrapDef 13 }

vServerFileSystemErrorClear  NOTIFICATION-TYPE
    OBJECTS    { mCode, errorCode, systemId, trapSeverity, entityId }
    STATUS    current
    DESCRIPTION
        " Trap issued to indicate that the earlier problem with file system
         access has been cleared."

    --#TYPE      "File System Error Clear"
    --#SUMMARY   "VenturiServer:  Clear to the File System access problem. "
    --#SUMMARY   "No action; Venturi has returned to normal operation."
    --#SEVERITY INFORMATIONAL
    ::= { vServerTrapDef 14 }

vServerTCPOverload  NOTIFICATION-TYPE
    OBJECTS    { mCode, errorCode, systemId, trapSeverity, 
                 currentValue, setThreshold, clearThreshold, entityId }
    STATUS    current
    DESCRIPTION
        " Trap issued when the threshold for the TCP bandwidth has been
         exceeded on this server.  The trap includes the current bandwidth
         usage (currentValue) and the set and clear thresholds, all of 
         which are expressed as percentages of the server's rated capacity. "
         
    --#TYPE      "TCP Overload"
    --#SUMMARY   "VenturiServer: TCP Overload; bandwidth over %d percent of rated capacity. "
    --#SUMMARY   "Consider installing addition Venturi capacity."
    --#ARGUMENTS  { 5 }
    --#SEVERITY MAJOR
    ::= { vServerTrapDef 15 }

vServerTCPOverloadClear  NOTIFICATION-TYPE
    OBJECTS    { mCode, errorCode, systemId, trapSeverity, entityId }
    STATUS    current
    DESCRIPTION
        " Trap issued to indicate that the Venturi servers' TCP bandwidth
        utilization has dropped below the alarm threshold."

    --#TYPE      "TCP Overload Clear"
    --#SUMMARY   "VenturiServer: Clear to TCP overload condition. "
    --#SUMMARY   "No action; Venturi has returned to normal operation."
    --#SEVERITY INFORMATIONAL
    ::= { vServerTrapDef 16 }

vServerCacheOverload NOTIFICATION-TYPE
    OBJECTS    { mCode, errorCode, systemId, trapSeverity, 
                 disk, currentValue, setThreshold, clearThreshold, entityId }
    STATUS    current
    DESCRIPTION
        " Trap issued when the free space on cache partition drops under the set 
        threshold.  For reference, the trap includes the name of the file system
        (disk) containing the cache, the current percent free (currentValue) and 
        the set and clear thresholds for the overload condition."

    --#TYPE      "Cache Overload"
    --#SUMMARY   "VenturiServer: Free cache space is under %d percent for partition: %s. "
    --#SUMMARY   "Contact Venturi."
    --#ARGUMENTS  { 6, 4 }
    --#SEVERITY MINOR
    ::= { vServerTrapDef 17 }

vServerCacheOverloadClear  NOTIFICATION-TYPE
    OBJECTS    { mCode, errorCode, systemId, trapSeverity, entityId }
    STATUS    current
    DESCRIPTION
        "Trap issued to indicate that cache free space has returned to 
        an acceptable level. "

    --#TYPE      "Cache Overload Clear"
    --#SUMMARY   "VenturiServer: Clear to free cache space problem. "
    --#SUMMARY   "No action; Venturi has returned to normal operation."
    --#SEVERITY INFORMATIONAL
    ::= { vServerTrapDef 18 }

vServerLogOverload NOTIFICATION-TYPE
    OBJECTS    { mCode, errorCode, systemId, trapSeverity, 
                 disk, currentValue, setThreshold, clearThreshold, entityId }
    STATUS    current
    DESCRIPTION
        " Trap issued when the free space on log partition is under the set 
        threshold.  For reference, the trap includes the name of the file system
        (disk) containing the logs, the current percent free (currentValue) and 
        the sent and clear thresholds for the overload condition. "

    --#TYPE      "Log Overload"
    --#SUMMARY   "VenturiServer: Free log space is under %d percent for partition: %s. "
    --#SUMMARY   "No action necessary; Venturi actively manages log space."
    --#ARGUMENTS  { 6, 4 }
    --#SEVERITY MINOR
    ::= { vServerTrapDef 19 }

vServerLogOverloadClear  NOTIFICATION-TYPE
    OBJECTS    { mCode, errorCode, systemId, trapSeverity, entityId }
    STATUS    current
    DESCRIPTION
        "Trap issued to indicate that the earlier problem with free log space has 
        been cleared. "

    --#TYPE      "Log Overload Clear"
    --#SUMMARY   "VenturiServer: Clear to free log space problem. "
    --#SUMMARY   "No action; Venturi has returned to normal operation."
    --#SEVERITY INFORMATIONAL
    ::= { vServerTrapDef 20 }

vServerFanFailure NOTIFICATION-TYPE
    OBJECTS    { mCode, errorCode, systemId, trapSeverity, 
                 fan, currentValue, setThreshold, clearThreshold, entityId }
    STATUS    current
    DESCRIPTION
        " Trap issued when the speed of one of the fans falls below
          an acceptable threshold.  The trap indicates the failing fan (fan),
          current fan speed (currentValue) in RPMs and the set and clear
          threshold speeds."

    --#TYPE      "Fan Alarm"
    --#SUMMARY   "VenturiServer: Fan %s failing (current RPM=%d, should be above %d). "
    --#SUMMARY   "Contact Venturi.  Venturi hardware needs attention."
    --#ARGUMENTS  { 4, 5, 6 }
    --#SEVERITY CRITICAL
    ::= { vServerTrapDef 21 }

vServerFanFailureClear NOTIFICATION-TYPE
    OBJECTS    { mCode, errorCode, systemId, trapSeverity, entityId }
    STATUS    current
    DESCRIPTION
        " Trap issued after a fan failure,  when the operation of all 
        fans has returned to acceptable parameters. "

    --#TYPE      "Fan Alarm Clear"
    --#SUMMARY   "VenturiServer: Clear to fan failure problem. "
    --#SUMMARY   "No action; Venturi has returned to normal operation."
    --#SEVERITY INFORMATIONAL
    ::= { vServerTrapDef 22 }

vServerPowerSupplyFailure NOTIFICATION-TYPE
    OBJECTS    { mCode, errorCode, systemId, trapSeverity, 
                 powerSupplyLead, currentValue, lowThreshold, highThreshold,
                 entityId }
    STATUS    current
    DESCRIPTION
        " Trap issued when one of the voltages from the power
          supply is out of the unacceptable range.  The trap 
          indicates the voltage out of spec (powerSupplyLead),
          its current value (currentValue), and the high and 
          low thresholds for the acceptable range.
          Measures are in volts."

    --#TYPE      "Power Supply Alarm"
    --#SUMMARY   "VenturiServer: Supply Lead (%s) voltage bad (cur=%s, min=%s, max=%s). "
    --#SUMMARY   "Contact Venturi.  Venturi hardware needs attention."
    --#ARGUMENTS  { 4, 5, 6, 7 }
    --#SEVERITY CRITICAL
    ::= { vServerTrapDef 23 }

vServerPowerSupplyFailureClear NOTIFICATION-TYPE
    OBJECTS    { mCode, errorCode, systemId, trapSeverity, entityId }
    STATUS    current
    DESCRIPTION
        " Trap issued after a power supply failure,  when the voltage on all 
        power supply leads has returned to acceptable values. "

    --#TYPE      "Power Supply Failure Clear"
    --#SUMMARY   "VenturiServer: Clear to power supply failure problem. "
    --#SUMMARY   "No action; Venturi has returned to normal operation."
    --#SEVERITY INFORMATIONAL
    ::= { vServerTrapDef 24 }

vServerTemperatureExceeded NOTIFICATION-TYPE
    OBJECTS    { mCode, errorCode, systemId, trapSeverity,
                 temperatureSensor, currentValue, setThreshold, clearThreshold, 
                 entityId }
    STATUS    current
    DESCRIPTION
        " Trap issued when the temperature of the system exceeds an acceptable 
        level.  The trap includes the name of the sensor indicating excessive 
        heat, its current value and the maximum value allowed (threshold).  
        Temperatures are expressed in degrees Celsius."

    --#TYPE      "Temperature Alarm"
    --#SUMMARY   "VenturiServer: Temperature Sensor (%s) is too hot (cur %d deg.; max %d deg.). "
    --#SUMMARY   "Check for environmental problems: ambient temperature or obstructed airflow. "
    --#SUMMARY   "If no external cause is found, contact Venturi (hardware may need attention)."
    --#ARGUMENTS  { 4, 5, 6 }
    --#SEVERITY CRITICAL
    ::= { vServerTrapDef 25 }

vServerTemperatureExceededClear NOTIFICATION-TYPE
    OBJECTS    { mCode, errorCode, systemId, trapSeverity, entityId }
    STATUS    current
    DESCRIPTION
        " Trap issued after a temperature exceeded alarm,  when all sensors 
        are again reporting acceptable temperatures. "

    --#TYPE      "Temperature Exceeded Clear"
    --#SUMMARY   "VenturiServer: Clear to temperature failure problem. "
    --#SUMMARY   "No action; Venturi has returned to normal operation."
    --#SEVERITY INFORMATIONAL
    ::= { vServerTrapDef 26 }

vServerStatsDeliveryFailure  NOTIFICATION-TYPE
    OBJECTS    { mCode, errorCode, systemId, trapSeverity,
                 filename, ftpHost, ftpUser, ftpDirectory, timeout, retries,
                 entityId }
    STATUS    current
    DESCRIPTION
        "Trap generated due to problems related to uploading statistics to 
        the configured FTP server.  The trap includes the name of the file 
        which failed to upload, the server to which upload was attempted
        (ftpHost), the user name used to authenticate with that server
        (ftpUser), the directory on that server to which the file was to
        be uploaded (ftpDirectory), the timeout used between attempts to 
        deliver and the number of retries attempted."

    --#TYPE      "Statistics Delivery Failure"
    --#SUMMARY   "VenturiServer: Statistics collection failure. "
    --#SUMMARY   "Check network access to configured FTP target system."
    --#SEVERITY MINOR
    ::= { vServerTrapDef 27 }

vServerStatsDeliveryClear  NOTIFICATION-TYPE
    OBJECTS    { mCode, errorCode, systemId, trapSeverity, entityId }
    STATUS    current
    DESCRIPTION
        "Trap generated when a previously reported statistics collection
        failure has been corrected and statistics collection has resumed."

    --#TYPE      "Statistics Deliver Failure Clear"
    --#SUMMARY   "VenturiServer: Clear to statistics collection failure. "
    --#SUMMARY   "No action; Venturi has returned to normal operation."
    --#SEVERITY INFORMATIONAL
    ::= { vServerTrapDef 28 }

vServerLogDeliveryFailure NOTIFICATION-TYPE
    OBJECTS    { mCode, errorCode, systemId, trapSeverity,
                 filename, ftpHost, ftpUser, ftpDirectory, timeout, retries,
                 entityId }
    STATUS    current
    DESCRIPTION
        "Trap generated due to problems related to uploading event logs to 
        the configured FTP server.  The trap includes the name of the file 
        which failed to upload, the server to which upload was attempted
        (ftpHost), the user name used to authenticate with that server
        (ftpUser), the directory on that server to which the file was to
        be uploaded (ftpDirectory), the timeout used between attempts to 
        deliver and the number of retries attempted."

    --#TYPE      "Log Delivery Failure"
    --#SUMMARY   "VenturiServer: Log collection failure. "
    --#SUMMARY   "Check network access to configured FTP target system."
    --#SEVERITY MINOR
    ::= { vServerTrapDef 29 }

vServerLogDeliveryClear  NOTIFICATION-TYPE
    OBJECTS    { mCode, errorCode, systemId, trapSeverity, entityId }
    STATUS    current
    DESCRIPTION
        "Trap generated when a previously reported log collection
        failure has been corrected and log collection has resumed."

    --#TYPE      "Log Deliver Failure Clear"
    --#SUMMARY   "VenturiServer: Clear to log collection failure. "
    --#SUMMARY   "No action; Venturi has returned to normal operation."
    --#SEVERITY INFORMATIONAL
    ::= { vServerTrapDef 30 }

vServerURLDeliveryFailure  NOTIFICATION-TYPE
    OBJECTS    { mCode, errorCode, systemId, trapSeverity,
                 filename, ftpHost, ftpUser, ftpDirectory, timeout, retries,
                 entityId }
    STATUS    current
    DESCRIPTION
        "Trap generated due to problems related to uploading event URL logs to 
        the configured FTP server.  The trap includes the name of the file 
        which failed to upload, the server to which upload was attempted
        (ftpHost), the user name used to authenticate with that server
        (ftpUser), the directory on that server to which the file was to
        be uploaded (ftpDirectory), the timeout used between attempts to 
        deliver and the number of retries attempted."

    --#TYPE      "URL Log Delivery Failure"
    --#SUMMARY   "VenturiServer: URL Log collection failure. "
    --#SUMMARY   "Check network access to configured FTP target system."
    --#SEVERITY MINOR
    ::= { vServerTrapDef 31 }

vServerURLDeliveryClear  NOTIFICATION-TYPE
    OBJECTS    { mCode, errorCode, systemId, trapSeverity, entityId }
    STATUS    current
    DESCRIPTION
        "Trap generated when a previously reported URL log collection
        failure has been corrected and URL log collection has resumed."

    --#TYPE      "URL Delivery Failure Clear"
    --#SUMMARY   "VenturiServer: Clear to URL Log collection failure. "
    --#SUMMARY   "No action; Venturi has returned to normal operation."
    --#SEVERITY INFORMATIONAL
    ::= { vServerTrapDef 32 }

vServerModuleInitFailure NOTIFICATION-TYPE
    OBJECTS    { mCode, errorCode, systemId, trapSeverity, entityId }
    STATUS    current
    DESCRIPTION
        " Trap issued when Venturi is starting and a module
          fails to initialize."

    --#TYPE      "Module Initialization Error"
    --#SUMMARY   "VenturiServer: Module failed to initialize. "
    --#SUMMARY   "Reboot server; if problem persists, contact Venturi."
    --#SEVERITY CRITICAL
    ::= { vServerTrapDef 33 }

vServerModuleInitFailureClear NOTIFICATION-TYPE
    OBJECTS    { mCode, errorCode, systemId, trapSeverity, entityId }
    STATUS    current
    DESCRIPTION
        " Trap issued after a vServerModuleInitFailure to indicate the
        problem has been cleared."

    --#TYPE      "Module Initialization Error Clear"
    --#SUMMARY   "VenturiServer: Module initialization failure has been cleared. "
    --#SUMMARY   "No action; Venturi has returned to normal operation."
    --#SEVERITY INFORMATIONAL
    ::= { vServerTrapDef 34 }

vServerDiskFailure NOTIFICATION-TYPE
    OBJECTS    { mCode, errorCode, systemId, trapSeverity, disk, entityId }
    STATUS    current
    DESCRIPTION
        " Trap issued on a failure of the hard disk.  The failing disk is
        indicated in the trap."

    --#TYPE      "Disk Failure"
    --#SUMMARY   "VenturiServer: Disk %s has failed. "
    --#SUMMARY   "Contact Venturi.  Venturi hardware needs attention."
    --#ARGUMENTS  { 4 }
    --#SEVERITY CRITICAL
    ::= { vServerTrapDef 35 }

vServerTestTrap NOTIFICATION-TYPE
    OBJECTS    { mCode, errorCode, systemId, trapSeverity, entityId }
    STATUS    current
    DESCRIPTION
        " Trap issued at user request.  The product user interface
          has an option to issue a test trap as a diagnostic tool. "

    --#TYPE      "Test Trap"
    --#SUMMARY   "VenturiServer: Test trap was generated. "
    --#SUMMARY   "No action.  This trap was sent at operator request."
    --#SEVERITY INFORMATIONAL
    ::= { vServerTrapDef 37 }


vServerLicensesExceeded NOTIFICATION-TYPE
    OBJECTS    { mCode, errorCode, systemId, trapSeverity, entityId }
    STATUS    current
    DESCRIPTION
        " Trap issued when the use of the system has exceeded
          the number of licenses purchased. "

    --#TYPE      "Licenses exceeded"
    --#SUMMARY   "VenturiServer: Licenses exceeded on system. "
    --#SUMMARY   "Consider installing addition Venturi capacity."
    --#SEVERITY MINOR
    ::= { vServerTrapDef 39 }


vServerRadiusServerError NOTIFICATION-TYPE
    OBJECTS    { mCode, errorCode, systemId, trapSeverity, radiusServer,
                 entityId }
    STATUS    current
    DESCRIPTION
        " Trap issued when we fail to connect to a RADIUS server."
    --#TYPE      "RADIUS server error"
    --#SUMMARY   "VenturiServer: Failed to connect to RADIUS server. "
    --#SUMMARY   "Check state of and connectivity to RADIUS server."
    --#SEVERITY MINOR
    ::= { vServerTrapDef 41 }


vServerRadiusServerErrorClear NOTIFICATION-TYPE
    OBJECTS    { mCode, errorCode, systemId, trapSeverity, entityId }
    STATUS    current
    DESCRIPTION
        " Trap issued when we succeed connecting to a RADIUS server
        after a previous failure."
    --#TYPE      "RADIUS server error clear"
    --#SUMMARY   "VenturiServer: RADIUS server error has been cleared. "
    --#SUMMARY   "No action; Venturi has returned to normal operation."
    --#SEVERITY MINOR
    ::= { vServerTrapDef 42 }

vServerLowCriticalBuffers NOTIFICATION-TYPE
    OBJECTS    { mCode, errorCode, systemId, trapSeverity, 
                 currentValue, setThreshold, clearThreshold, entityId }
    STATUS    current
    DESCRIPTION
        "The server is experiencing a critical low buffer condition.  While 
         in this condition new client connections will be rejected and only 
         in-sequence packets will be acknowledged.  This may be experienced
         as a slowdown in the server and is an indication that the server is
         operating beyond its capacity.  The trap includes the current number 
         of free buffers and the threshold.  When the server's free buffer 
         level drops below this threshold the server enters this condition."
    --#TYPE      "Low buffer condition"
    --#SUMMARY   "VenturiServer: the server is in a low buffer state.  "
    --#SUMMARY   "If this condition does not clear when traffic levels lower, "
    --#SUMMARY   "reboot the server.  If this condition clears as traffic levels "
    --#SUMMARY   "lower and this condition  occurs frequently, consider "
    --#SUMMARY   "installing additional Venturi capacity."
    --#SEVERITY CRITICAL
    ::= { vServerTrapDef 43 }

vServerLowCriticalBuffersClear NOTIFICATION-TYPE
    OBJECTS    { mCode, errorCode, systemId, trapSeverity, entityId }
    STATUS    current
    DESCRIPTION
        " Trap issued when the server normal buffer reserves have been restored."
    --#SUMMARY   "VenturiServer: the server has returned to normal free buffer levels. "
    --#SUMMARY   "No action; Venturi has returned to normal operation."
    ::= { vServerTrapDef 44 }

vServerClientStatsDeliveryFailure  NOTIFICATION-TYPE
    OBJECTS    { mCode, errorCode, systemId, trapSeverity,
                 filename, ftpHost, ftpUser, ftpDirectory, timeout, retries,
                 entityId }
    STATUS    current
    DESCRIPTION
        "Trap generated due to problems related to uploading client statistics 
        to the configured FTP server.  The trap includes the name of the file 
        which failed to upload, the server to which upload was attempted
        (ftpHost), the user name used to authenticate with that server
        (ftpUser), the directory on that server to which the file was to
        be uploaded (ftpDirectory), the timeout used between attempts to 
        deliver and the number of retries attempted."

    --#TYPE      "Statistics Delivery Failure"
    --#SUMMARY   "VenturiServer: Statistics collection failure. "
    --#SUMMARY   "Check network access to configured FTP target system."
    --#SEVERITY MINOR
    ::= { vServerTrapDef 45 }

vServerClientStatsDeliveryClear  NOTIFICATION-TYPE
    OBJECTS    { mCode, errorCode, systemId, trapSeverity, entityId }
    STATUS    current
    DESCRIPTION
        "Trap generated when a previously reported client statistics collection
        failure has been corrected and statistics collection has resumed."

    --#TYPE      "Client Statistics Delivery Failure Clear"
    --#SUMMARY   "VenturiServer: Clear to client statistics collection failure. "
    --#SUMMARY   "No action; Venturi has returned to normal operation."
    --#SEVERITY INFORMATIONAL
    ::= { vServerTrapDef 46 }

vServerClientUpgradeDeliveryFailure  NOTIFICATION-TYPE
    OBJECTS    { mCode, errorCode, systemId, trapSeverity,
                 filename, ftpHost, ftpUser, ftpDirectory, timeout, retries,
                 entityId }
    STATUS    current
    DESCRIPTION
        "Trap generated due to problems related to uploading client upgrade 
        to the configured FTP server.  The trap includes the name of the file 
        which failed to upload, the server to which upload was attempted
        (ftpHost), the user name used to authenticate with that server
        (ftpUser), the directory on that server to which the file was to
        be uploaded (ftpDirectory), the timeout used between attempts to 
        deliver and the number of retries attempted."

    --#TYPE      "Client Autoupgrade Delivery Failure"
    --#SUMMARY   "VenturiServer: Client Autoupgrade collection failure. "
    --#SUMMARY   "Check network access to configured FTP target system."
    --#SEVERITY MINOR
    ::= { vServerTrapDef 47 }

vServerClientUpgradeDeliveryClear  NOTIFICATION-TYPE
    OBJECTS    { mCode, errorCode, systemId, trapSeverity, entityId }
    STATUS    current
    DESCRIPTION
        "Trap generated when a previously reported client upgrade collection
        failure has been corrected and statistics collection has resumed."

    --#TYPE      "Client Autoupgrade Delivery Failure Clear"
    --#SUMMARY   "VenturiServer: Clear to client autoupgrade collection failure. "
    --#SUMMARY   "No action; Venturi has returned to normal operation."
    --#SEVERITY INFORMATIONAL
    ::= { vServerTrapDef 48 }

vServerDCDeliveryFailure  NOTIFICATION-TYPE
    OBJECTS    { mCode, errorCode, systemId, trapSeverity,
                 filename, ftpHost, ftpUser, ftpDirectory, timeout, retries,
                 entityId }
    STATUS    current
    DESCRIPTION
        "Trap generated due to problems related to uploading disconnection logs to 
        the configured FTP server.  The trap includes the name of the file 
        which failed to upload, the server to which upload was attempted
        (ftpHost), the user name used to authenticate with that server
        (ftpUser), the directory on that server to which the file was to
        be uploaded (ftpDirectory), the timeout used between attempts to 
        deliver and the number of retries attempted."

    --#TYPE      "DC Log Delivery Failure"
    --#SUMMARY   "VenturiServer: DC Log collection failure. "
    --#SUMMARY   "Check network access to configured FTP target system."
    --#SEVERITY MINOR
    ::= { vServerTrapDef 49 }

vServerDCDeliveryClear  NOTIFICATION-TYPE
    OBJECTS    { mCode, errorCode, systemId, trapSeverity, entityId }
    STATUS    current
    DESCRIPTION
        "Trap generated when a previously reported DC log collection
        failure has been corrected and DC log collection has resumed."

    --#TYPE      "DC Log Delivery Failure Clear"
    --#SUMMARY   "VenturiServer: Clear to DC Log collection failure. "
    --#SUMMARY   "No action; Venturi has returned to normal operation."
    --#SEVERITY INFORMATIONAL
    ::= { vServerTrapDef 50 }

-- ----------------------------
--  End Trap definitions
-- ----------------------------

-- ----------------------------
--  Trap Information
--
--   The objects in this section are not accessible, but describe objects
--   sent as extra information with one or more of the traps defined above.
-- ----------------------------

errorCode OBJECT-TYPE
    SYNTAX        Integer32
    MAX-ACCESS    accessible-for-notify
    STATUS        current
    DESCRIPTION
        "Error code associated with the trap."
    ::= { vServerTrapInfo 1 }

filename OBJECT-TYPE
    SYNTAX        OCTET STRING (SIZE(1..128))
    MAX-ACCESS    accessible-for-notify
    STATUS        current
    DESCRIPTION
        "Filename associated with the trap."
    ::= { vServerTrapInfo 2 }

fan OBJECT-TYPE
    SYNTAX        OCTET STRING (SIZE(1..128))
    MAX-ACCESS    accessible-for-notify
    STATUS        current
    DESCRIPTION
        "A string identifying the failing fan."
    ::= { vServerTrapInfo 3 }

mCode OBJECT-TYPE
    SYNTAX        Integer32
    MAX-ACCESS    accessible-for-notify
    STATUS        current
    DESCRIPTION
        "Major code associated with the trap."
    ::= { vServerTrapInfo 4 }

currentValue OBJECT-TYPE
    SYNTAX        OCTET STRING (SIZE(1..128))
    MAX-ACCESS    accessible-for-notify
    STATUS        current
    DESCRIPTION
        "The current value of the measure determining the condition."
    ::= { vServerTrapInfo 5 }

disk OBJECT-TYPE
    SYNTAX        OCTET STRING (SIZE(1..128))
    MAX-ACCESS    accessible-for-notify
    STATUS        current
    DESCRIPTION
        "Disk associated with trap."
    ::= { vServerTrapInfo 7 }

powerSupplyLead OBJECT-TYPE
    SYNTAX        OCTET STRING (SIZE(1..128))
    MAX-ACCESS    accessible-for-notify
    STATUS        current
    DESCRIPTION
        "Power supply lead associated with trap."
    ::= { vServerTrapInfo 8 }

systemId OBJECT-TYPE
    SYNTAX        OCTET STRING (SIZE(1..128))
    MAX-ACCESS    accessible-for-notify
    STATUS        current
    DESCRIPTION
        "Unique system identifier.  Value used currently is MAC address of eth0."
    ::= { vServerTrapInfo 9 }

temperatureSensor OBJECT-TYPE
    SYNTAX        OCTET STRING (SIZE(1..128))
    MAX-ACCESS    accessible-for-notify
    STATUS        current
    DESCRIPTION
        "The name of the temperature sensor.  This is used with the 
        vServerTemperatureExceeded trap."
    ::= { vServerTrapInfo 10 }

trapSeverity OBJECT-TYPE
    SYNTAX        INTEGER {
                      critical(1),
                      major(2),
                      minor(3),
                      warning(4),
                      informational(5)
                  }
    MAX-ACCESS    accessible-for-notify
    STATUS        current
    DESCRIPTION
         "This is a varbind in every Venturi enterprise trap.  It
         indicates the configured severity of the incident being
         reported."
    ::= { vServerTrapInfo 11 }

ftpHost OBJECT-TYPE
    SYNTAX        OCTET STRING (SIZE(1..128))
    MAX-ACCESS    accessible-for-notify
    STATUS        current
    DESCRIPTION
         "The FTP host having a problem with a file upload."
    ::= { vServerTrapInfo 12 }

ftpUser OBJECT-TYPE
    SYNTAX        OCTET STRING (SIZE(1..128))
    MAX-ACCESS    accessible-for-notify
    STATUS        current
    DESCRIPTION
         "The FTP user having a problem with a file upload."
    ::= { vServerTrapInfo 13 }

ftpDirectory OBJECT-TYPE
    SYNTAX        OCTET STRING (SIZE(1..128))
    MAX-ACCESS    accessible-for-notify
    STATUS        current
    DESCRIPTION
         "The FTP directory having a problem with a file upload."
    ::= { vServerTrapInfo 14 }

timeout OBJECT-TYPE
    SYNTAX        Integer32
    MAX-ACCESS    accessible-for-notify
    STATUS        current
    DESCRIPTION
         "The timeout interval in FTP upload configuration."
    ::= { vServerTrapInfo 15 }

retries OBJECT-TYPE
    SYNTAX        Integer32
    MAX-ACCESS    accessible-for-notify
    STATUS        current
    DESCRIPTION
         "The retries in FTP upload configuration."
    ::= { vServerTrapInfo 16 }

radiusServer OBJECT-TYPE
    SYNTAX        OCTET STRING (SIZE(1..128))
    MAX-ACCESS    accessible-for-notify
    STATUS        current
    DESCRIPTION
         "The address or name of the RADIUS server."
    ::= { vServerTrapInfo 17 }

setThreshold OBJECT-TYPE
    SYNTAX        OCTET STRING (SIZE(1..128))
    MAX-ACCESS    accessible-for-notify
    STATUS        current
    DESCRIPTION
         "Threshold passed to cause a condition to be set.
          The condition may be set by a measure falling below
          this threshold or rising above it.  The description
          of the specific trap will indicate which."
    ::= { vServerTrapInfo 18 }

clearThreshold OBJECT-TYPE
    SYNTAX        OCTET STRING (SIZE(1..128))
    MAX-ACCESS    accessible-for-notify
    STATUS        current
    DESCRIPTION
         "Threshold passed to cause a condition to be cleared.
          The condition may be cleared by a measure falling below
          this threshold or rising above it.  The description
          of the specific trap will indicate which."
    ::= { vServerTrapInfo 19 }

highThreshold OBJECT-TYPE
    SYNTAX        OCTET STRING (SIZE(1..128))
    MAX-ACCESS    accessible-for-notify
    STATUS        current
    DESCRIPTION
         "Threshold passed to cause a condition to be set.
         High and low thresholds are used for conditions which
         are set when a measure falls outside of a range considered
         normal.  The normal range is defined to be between the
         high and low thresholds."
    ::= { vServerTrapInfo 20 }

lowThreshold OBJECT-TYPE
    SYNTAX        OCTET STRING (SIZE(1..128))
    MAX-ACCESS    accessible-for-notify
    STATUS        current
    DESCRIPTION
         "Threshold passed to cause a condition to be set.
         High and low thresholds are used for conditions which
         are set when a measure falls outside of a range considered
         normal.  The normal range is defined to be between the
         high and low thresholds."
    ::= { vServerTrapInfo 21 }

entityId OBJECT-TYPE
    SYNTAX        Integer32
    MAX-ACCESS    accessible-for-notify
    STATUS        current
    DESCRIPTION
         "The entityId will be a common value for the set and clear
          traps anouncing entry to and exit from some condition,
          possibly an error condition.  For set and clear traps, 
          the value of this object will correspond to the 
          vServerConditionType in the vServerConditionTable.
          For stand-alone traps (those not not associated with
          the setting or clearing of an error condition) the
          value of entityId will always be zero."
    ::= { vServerTrapInfo 22 }

END
