LINKSYS-ENDOFMIB-MIB DEFINITIONS ::= BEGIN

-- Title:                LINKSYS ROS
--                       Private End of MIB MIB
-- Version:              7.46
-- Date:                 15-Jan-2007

IMPORTS
    rnd                                                     FROM LINKSYS-MIB
    OBJECT-TYPE, MODULE-IDENTITY                            FROM SNMPv2-SMI;

rndEndOfMibGroup MODULE-IDENTITY
                LAST-UPDATED "200701020000Z"
                ORGANIZATION "
                              Linksys LLC."
                CONTACT-INFO
                      "www.linksys.com/business/support"
                DESCRIPTION
                      "This private MIB module defines End of MIB private MIBs."
                REVISION "200701020000Z"
                DESCRIPTION
                      "Initial revision."
        ::= { rnd 1000 }

rndEndOfMib OBJECT-TYPE
      SYNTAX  INTEGER
      MAX-ACCESS   read-only
      STATUS   current
      DESCRIPTION
        " This variable indicates this is the end of RND MIB."
      ::= {  rndEndOfMibGroup 1  }

END
